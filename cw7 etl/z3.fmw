FME workspace z3.fmw

Parameters:
- SourceDataset_SHAPEFILE = D:\Pobrane\vectors\Data\GB\scotland_and_wales_region.shp   # Source Esri Shapefile(s)
- SourceDataset_GEOTIFF = ""D:\Pobrane\ras250_gb\data\HP.tif" "D:\Pobrane\ras250_gb\data\HT.tif" "D:\Pobrane\ras250_gb\data\HU.tif" "D:\Pobrane\ras250_gb\data\HW.tif" "D:\Pobrane\ras250_gb\data\HX.tif" "D:\Pobrane\ras250_gb\data\HY.tif" "D:\Pobrane\ras250_gb\data\HZ.tif" "D:\Pobrane\ras250_gb\data\NA.tif" "D:\Pobrane\ras250_gb\data\NB.tif" "D:\Pobrane\ras250_gb\data\NC.tif" "D:\Pobrane\ras250_gb\data\ND.tif" "D:\Pobrane\ras250_gb\data\NF.tif" "D:\Pobrane\ras250_gb\data\NG.tif" "D:\Pobrane\ras250_gb\data\NH.tif" "D:\Pobrane\ras250_gb\data\NJ.tif" "D:\Pobrane\ras250_gb\data\NK.tif" "D:\Pobrane\ras250_gb\data\NL.tif" "D:\Pobrane\ras250_gb\data\NM.tif" "D:\Pobrane\ras250_gb\data\NN.tif" "D:\Pobrane\ras250_gb\data\NO.tif" "D:\Pobrane\ras250_gb\data\NR.tif" "D:\Pobrane\ras250_gb\data\NS.tif" "D:\Pobrane\ras250_gb\data\NT.tif" "D:\Pobrane\ras250_gb\data\NU.tif" "D:\Pobrane\ras250_gb\data\NW.tif" "D:\Pobrane\ras250_gb\data\NX.tif" "D:\Pobrane\ras250_gb\data\NY.tif" "D:\Pobrane\ras250_gb\data\NZ.tif" "D:\Pobrane\ras250_gb\data\OV.tif" "D:\Pobrane\ras250_gb\data\SC.tif" "D:\Pobrane\ras250_gb\data\SD.tif" "D:\Pobrane\ras250_gb\data\SE.tif" "D:\Pobrane\ras250_gb\data\SH.tif" "D:\Pobrane\ras250_gb\data\SJ.tif" "D:\Pobrane\ras250_gb\data\SK.tif" "D:\Pobrane\ras250_gb\data\SM.tif" "D:\Pobrane\ras250_gb\data\SN.tif" "D:\Pobrane\ras250_gb\data\SO.tif" "D:\Pobrane\ras250_gb\data\SP.tif" "D:\Pobrane\ras250_gb\data\SR.tif" "D:\Pobrane\ras250_gb\data\SS.tif" "D:\Pobrane\ras250_gb\data\ST.tif" "D:\Pobrane\ras250_gb\data\SU.tif" "D:\Pobrane\ras250_gb\data\SV.tif" "D:\Pobrane\ras250_gb\data\SW.tif" "D:\Pobrane\ras250_gb\data\SX.tif" "D:\Pobrane\ras250_gb\data\SY.tif" "D:\Pobrane\ras250_gb\data\SZ.tif" "D:\Pobrane\ras250_gb\data\TA.tif" "D:\Pobrane\ras250_gb\data\TF.tif" "D:\Pobrane\ras250_gb\data\TG.tif" "D:\Pobrane\ras250_gb\data\TL.tif" "D:\Pobrane\ras250_gb\data\TM.tif" "D:\Pobrane\ras250_gb\data\TQ.tif" "D:\Pobrane\ras250_gb\data\TR.tif" "D:\Pobrane\ras250_gb\data\TV.tif""   # Source GeoTIFF File(s) or URL(s)
- DestDataset_POSTGIS_RASTER = cw9   # Connection

Readers:
- SHAPEFILE_1: SHAPEFILE from $(SourceDataset_SHAPEFILE)
- GEOTIFF_1: GEOTIFF from $(SourceDataset_GEOTIFF)

Writers:
- POSTGIS_RASTER_1: POSTGIS_RASTER to $(DestDataset_POSTGIS_RASTER)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE = CASE_INSENSITIVE_TEST @Value(NAME) BEGINS_WITH South Wales
    TEST_MODE = TEST
    PASSED -> Aggregator
Aggregator
    ACCUM_ATTRS_NAME = Use Attributes From One Feature
    AGGREGATE_TYPE = Homogeneous Collection (If Possible)
    MODE = Geometry - Assemble One Level
    SEP = ,
    AGGREGATE -> Clipper [CLIPPER]
GEOTIFF (reader GEOTIFF_1)
    -> Clipper [CANDIDATE]
Clipper
    ADD_NODATA = YES
    ATTR_ACCUM_MODE = MERGE
    ATTR_CONFLICT_RES = CANDIDATE
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = YES
    RASTER_CELL_MODE = CENTER
    Z_VAL_SOURCE = CANDIDATE
    INSIDE -> RasterPaletteResolver
RasterPaletteResolver
    -> Exports (writer POSTGIS_RASTER_1)
Exports (writer POSTGIS_RASTER_1)
